/*
  Root package: replace ProjectName, imports. List this file LAST in config.yaml model_files.
*/
package ProjectName {
  private import ProjectNameRequirements::*;
  private import ProjectNameMain::*;
  // private import ProjectNameBehaviour::*;
}
