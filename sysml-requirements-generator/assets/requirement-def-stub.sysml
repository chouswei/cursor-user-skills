/*
  Stub: replace PackageNameRequirements, ReqExample, R#, doc text.
*/
package PackageNameRequirements {
  private import ScalarValues::String;

  requirement def ReqExample {
    attribute requirementId : String = "R1";
    doc /*
      The system SHALL … (normative statement).
    */
  }
}
